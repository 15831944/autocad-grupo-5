(defun c:puntos	()
  (setq mode (getvar "pdmode"))
  (setvar "pdmode" 35)
  (setq	archpuntos (getfiled "Archivos de puntos" (getvar "dwgprefix") "txt" 16))
  (setq archivo (open archpuntos "r"))
  (while (/= nil    (setq punto (read-line archivo)))
	     (command "point" punto)
  )
  (close archivo)
;;;  (setvar "pdmode" mode)
)
