(defun circulo ()
  (setq p1 (getpoint "Indique el centro de la circumferencia"))
  (terpri)
  (setq radio (getreal "radio de la circumferencia: "))
  (Command "circle" p1 radio)
)
xxxxxxxxxxxxxxxxxxxxxxxxxxxxxxxxxxxxxxxxxxxxxxxxxxxxxxxxxxxxxxxxxxxxxxx
(defun rectangulo ()
  (setq p1 (getpoint "Indique la esquina inferior"))
  (terpri)
  (setq p2 (getpoint p1 "Indique la esquina superior"))
  (terpri)
  (Command "rectangle" p1 p2)
)
xxxxxxxxxxxxxxxxxxxxxxxxxxxxxxxxxxxxxxxxxxxxxxxxxxxxxxxxxxxxxxxxxxxxxxxx
(defun pentagono ()
  (setq p1 (getpoint "Indique el centro del pentagono"))
  (terpri)
  (setq p2 (getpoint p1 "Indique la media de la distancia"))
  (terpri)
  (Command "polygon" "5" p1 "i" p2)
)
xxxxxxxxxxxxxxxxxxxxxxxxxxxxxxxxxxxxxxxxxxxxxxxxxxxxxxxxxxxxxxxxxxxxxxxx
(defun exagono ()
  (setq p1 (getpoint "Indique el centro del exagono"))
  (terpri)
  (setq p2 (getpoint p1 "Indique la media de la distancia"))
  (terpri)
  (Command "polygon" "6" p1 "i" p2)
)
xxxxxxxxxxxxxxxxxxxxxxxxxxxxxxxxxxxxxxxxxxxxxxxxxxxxxxxxxxxxxxxxxxxxxxxx
(defun triangulo ()
  (setq p1 (getpoint "Indique el centro del triangulo"))
  (terpri)
  (setq p2 (getpoint p1 "Indique la media de la distancia"))
  (terpri)
  (Command "polygon" "3" p1 "i" p2)
)
xxxxxxxxxxxxxxxxxxxxxxxxxxxxxxxxxxxxxxxxxxxxxxxxxxxxxxxxxxxxxxxxxxxxxxxx
(defun c:poligono ()
  (initget 1 "Triangulo Rectangulo Circulo Pentagono Exagono")
  (setq	tipo
	 (getkword
	   "que tipo de poligono desea <Triangulo/Rectangulo/Pentagono/Exagono/Circulo: "
	 )
  )
  (cond
    ((= tipo "Triangulo") (triangulo))
    ((= tipo "Rectangulo") (rectangulo))
    ((= tipo "Circulo") (circulo))
    ((= tipo "Pentagono") (pentagono))
    ((= tipo "Exagono") (exagono))
  )
)
