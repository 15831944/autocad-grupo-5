(DEFUN C:ATTPER ()
  (SETQ E1 (CAR (ENTSEL)))
  (WHILE (/= "SEQEND" (CDR (ASSOC 0 (SETQ PROXIMO (ENTGET (SETQ E1 (ENTNEXT E1)))))))
    (IF (= "ATTRIB" (CDR (ASSOC 0 PROXIMO)))
	    (PROGN
	      (IF (= "DATO" (CDR (ASSOC 2 PROXIMO)))
		(SETQ nombre (CDR (ASSOC 1 PROXIMO)))
	      )
	      (IF (= "CANTIDAD" (CDR (ASSOC 2 PROXIMO)))
		(SETQ VALOR (CDR (ASSOC 1 PROXIMO)))
	      )
	    )
    )
  )
  (alert (strcat "El codigo es: " NOMBRE "\nEl valor es: " VALOR))
)
