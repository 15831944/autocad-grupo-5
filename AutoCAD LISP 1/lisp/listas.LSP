(Defun c:rec2 ()
  (setq p1 (getpoint "\nIngrese el primer punto... ")
	p3 (getpoint "\nIngrese el segundo punto... ")
  )
  (setq p1x (car p1)
	p1y (cadr p1)
	p3x (car p3)
	p3y (cadr p3)
  )
  (setq p2 (list p3x p1y)
	p4 (list p1x p3y)
  )
  (setq dist (/ (distance p1 p3) 2)
	angulo (angle p1 p3)
	p5 (polar p1 angulo dist)
  )
  (command "_pline" p1 p2 p3 p4 "c")
  (command "area" "o" "l")
  (setq medida (strcat "El Area es: " (rtos (getvar "area") 2 2) " m2"))
  (command "text" "j" "m" p5 (* dist 0.04) 0 medida)
)
