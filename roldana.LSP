(defun capa (nombre color)
  (ENTMAKE (LIST
    (CONS 0 "LAYER")
    (CONS 100 "AcDbSymbolTableRecord")
    (CONS 100 "AcDbLayerTableRecord")
    (CONS 2 nombre)
    (CONS 70 0)
    (CONS 62 color)
    (CONS 6 "CONTINUOUS")
    )
  )
)

(defun crear_hueco_tornillo (punto multi)
  (setq oldLayer (getvar "CLAYER"))
  (setvar "CLAYER" "aux" )
  (command "cylinder" punto (* multi 4) (* multi -10) )
  (setq cil (entlast))
  (command "cone" punto (* multi 8) (* multi -10) )
  (setq con (entlast))
  (command "union" cil con "" )
  (setvar "CLAYER" oldLayer )
  )

(defun crear_base (pt multi)
  (setq oldLayer (getvar "CLAYER"))
  (setvar "CLAYER" "base" )
  (command "pline"
	   (list 	(+ (car pt)(* multi 20))	(cadr pt)	(caddr pt))
	   (list 	(+ (car pt)(* multi 130))	(cadr pt)	(caddr pt) )
	   "A" (list 	(+ (car pt)(* multi 150))	(+ (cadr pt)(* multi 20))	(caddr pt))
	   "L" (list 	(+ (car pt)(* multi 150))	(+ (cadr pt)(* multi 80))	(caddr pt))
	   "A" (list 	(+ (car pt)(* multi 130))	(+ (cadr pt)(* multi 100))	(caddr pt))
	   "L" (list 	(+ (car pt)(* multi 20))	(+ (cadr pt)(* multi 100))	(caddr pt))
	   "A" (list 	(car pt) 	(+ (cadr pt)(* multi 80))	(caddr pt))
	   "L" (list 	(car pt)	(+ (cadr pt)(* multi 20)) 	(caddr pt))
	   "A" (list 	(+ (car pt)(* multi 20))	(cadr pt) 	(caddr pt))
	   "close"
	   )
  (setq base (entlast))
  (command "extrude" base "" (* multi 10) 0 )
  (setvar "CLAYER" oldLayer)
  )

(defun crear_roldana (pt multi)
  (setq oldLayer (getvar "CLAYER"))
  (setq pto_toroide (list (car pt) (cadr pt) (+ (caddr pt) (* multi 12))) )
  (setvar "CLAYER" "roldana" )
  (command "cylinder" pt (* multi 50) (* multi 24) )
  (setq cil (entlast))
  (setvar "CLAYER" "aux" )
  (command "torus" pto_toroide (* 50 multi ) (* 8 multi ) )
  (setq tor (entlast))
  (command "subtract" cil "" tor "")

  (setvar "CLAYER" "roldana" )
  (command "cylinder" pto_toroide (* multi 20) (* multi 15) )
  (command "cylinder" pto_toroide (* multi 20) (* multi -15) )
  (command "cylinder" pto_toroide (* multi 10) (* multi 25) )
  (command "cylinder" pto_toroide (* multi 10) (* multi -25) )
  (setq capa_roldana (ssget "X" '((8 . "roldana")) ))
  (command "union" capa_roldana "" )
  (setvar "CLAYER" oldLayer)
  )

(defun crear_parante (pt multi)
  (setq oldLayer (getvar "CLAYER"))
  (setvar "CLAYER" "aux" )
  (command "pline" pt
	   (list (car pt) (+ (cadr pt)(* multi 80)) (caddr pt))
	   "A" (list (- (car pt)(* multi 20)) (+ (cadr pt)(* multi 100)) (caddr pt))
	   "L" (list (- (car pt)(* multi 80)) (+ (cadr pt)(* multi 100)) (caddr pt))
	   "A" (list (- (car pt)(* multi 100)) (+ (cadr pt)(* multi 80)) (caddr pt))
	   "L" (list (- (car pt)(* multi 100)) (cadr pt) (caddr pt))
	   pt "Close"
	   )
  (setq _parante (entlast))
  (command "extrude" _parante "" (* multi 10) 0 )
  (setq _parante_ (entlast))
  (command "cylinder" (list (- (car pt)(* multi 50))(+ (cadr pt)(* multi 75)) (caddr pt) ) (* multi 10) (* multi 10) )
  (setq cil (entlast))
  (command "subtract" _parante_ "" cil "")
  (setq parante_hueco (entlast))
  (command "change" parante_hueco "" "p" "la" "base" "")
  (setvar "CLAYER" oldLayer )
  )

(defun c:roldana ()
  (setq
    pt_i (getpoint "\nIngrese un punto de insercion: ")
    val (getreal "\nIngrese un radio exterior para la roldana: ")
    multi (/ val 50)
    )
  (command "ucs" "" "")
  (capa "aux" 1)
  (capa "base" 2)
  (capa "roldana" 3)

    ; seteo configuraciones
  (command "osmode" 0 )
  (command "surftab1" 20 )
  (command "surftab2" 20 )
  (command "isolines" 20 )


  (crear_base pt_i multi)

  (crear_hueco_tornillo (list (+ (car pt_i) (* multi 20)) (+ (cadr pt_i) (* multi 20)) (+ (caddr pt_i) (* 10 multi)) ) multi)
  (crear_hueco_tornillo (list (+ (car pt_i) (* multi 20)) (+ (cadr pt_i) (* multi 80)) (+ (caddr pt_i) (* 10 multi)) ) multi)
  (crear_hueco_tornillo (list (+ (car pt_i) (* multi 130)) (+ (cadr pt_i) (* multi 20)) (+ (caddr pt_i) (* 10 multi)) ) multi)
  (crear_hueco_tornillo (list (+ (car pt_i) (* multi 130)) (+ (cadr pt_i) (* multi 80)) (+ (caddr pt_i) (* 10 multi)) ) multi)

  (setq capa_aux (ssget "X" '((8 . "aux")) ))
  (setq capa_base (ssget "X" '((8 . "base")) ))

  (command "subtract" capa_base "" capa_aux "")
  (setq parante1_i (list (+ (car pt_i)(* multi 60)) (cadr pt_i)(+ (caddr pt_i)(* multi 10))) )
  (setq parante1_f (list (+ (car pt_i)(* multi 60)) (+(cadr pt_i)(* multi 100)) (+ (caddr pt_i)(* multi 10))) )
  (setq parante2_i (list (+ (car pt_i)(* multi 100)) (cadr pt_i)(+ (caddr pt_i)(* multi 10))) )
  (setq parante2_f (list (+ (car pt_i)(* multi 100)) (+(cadr pt_i)(* multi 100)) (+ (caddr pt_i)(* multi 10))) )
	

  (command "ucs" "za" parante1_i (list (car pt_i)(cadr pt_i)(+ (caddr pt_i)(* multi 10)) ) )

  (setvar "CLAYER" "base")
  (crear_parante (list 0 0 0) multi)
  (crear_parante (list 0 0 -40) multi)
  
  (command "union" (ssget "X") "")
  
  (crear_roldana (list -50 75 -27) multi )
  
  (command "ucs" "" "")
  (setq capa_aux (ssget "X" '((8 . "aux")) ))
  (command "change" capa_aux "" "p" "la" "base" "")
  )
