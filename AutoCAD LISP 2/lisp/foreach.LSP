(DEFUN CAPA (nombre color)
  (ENTMAKE (LIST
	     (CONS 0 "LAYER")
	     (CONS 100 "AcDbSymbolTableRecord")
	     (CONS 100 "AcDbLayerTableRecord")
	     (CONS 2 nombre)
	     (CONS 70 0)
	     (CONS 62 color)
	     (CONS 6 "CONTINUOUS")
	   )
  )	   
)
(defun c:capaper ()
  (setq listacapas (list
		     (list "fich01" 1)
		     (list "fich02" 2)
		     (list "fich03" 3)
		     (list "fich04" 4)
		     (list "fich05" 5)
		     (list "fich06" 6)
		   )
  )
  (FOREACH n listacapas
    (capa (car n)(cadr n))
  )
)
