(defun c:intr ()
  (setq archivo (findfile "d:/facultad/textos/archivo.txt")
 	abrirarchivo (open archivo "r")
	primer	     (read-line abrirarchivo)
	segunda	     (read-line abrirarchivo)
	tercera	     (read-line abrirarchivo)
  )
  (close archivo)
)
