(DEFUN AUXILIAR (VAR1 VAR2)
  (ALERT VAR1)
  (ALERT VAR2)
)
;;;XXXXXXXXXXXXXXXXXXXXXXXXXXXXXXXXX
(DEFUN C:PARA ()
  (SETQ A1 (GETSTRING "\nINGRESE EL PRIMER NOMBRE: "))
  (SETQ A2 (GETSTRING "\nINGRESE EL SEGUNDO NOMBRE: "))
  (AUXILIAR A1 A2)
)
