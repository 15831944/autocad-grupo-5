(defun terminaexcel ()
  (vlax-release-object *celdasexcel*)
  (vlax-release-object *hoja1*)
  (vlax-release-object *coleccionhojas*)
  (vlax-release-object *nuevolibro*)
  (vlax-release-object coleccionlibros*)
  (vlax-release-object *aplexcel*)
)
;;;xxxxxxxxxxxxxxxxxxxxxxxxxxxxxxxxxxxxxxxxxxxxxxxxxxxxxxxxxxxxxxxxxxx
(defun procesafila (fila numfila / numcol)
  (setq numcol 0)
  (foreach campo fila
    (Datocelda numfila (setq numcol (+ 1 numcol))
    (cdr campo))
  )
)
;;;xxxxxxxxxxxxxxxxxxxxxxxxxxxxxxxxxxxxxxxxxxxxxxxxxxxxxxxxxxxxxxxxxxx
(defun iniciaexcel ()
  (setq *aplexcel* (vlax-get-or-create-object "excel.application")
	*coleccionlibros* (vlax-get-property *aplexcel* "workbooks")
	*nuevolibro* (vlax-invoke-method *coleccionlibros* "add")
	*coleccionhojas* (vlax-get-property *nuevolibro* "sheets")
	*hoja1* (vlax-get-property *coleccionhojas* "item" 1)
	*celdasexcel* (vlax-get-property *hoja1* "cells")
  )
  (vla-put-visible *aplexcel* :vlax-true)
)
;;;xxxxxxxxxxxxxxxxxxxxxxxxxxxxxxxxxxxxxxxxxxxxxxxxxxxxxxxxxxxxxxxxxxx
(defun datocelda (fila col valor)
  (vlax-put-property *celdasexcel* "item" fila col
    (vl-princ-to-string valor)
  )
)
;;;xxxxxxxxxxxxxxxxxxxxxxxxxxxxxxxxxxxxxxxxxxxxxxxxxxxxxxxxxxxxxxxxxxx
(defun apl-err (msg)
  (terminaexcel)
  (prompt msg)
  (setq *error* oer)
)
  
;;;xxxxxxxxxxxxxxxxxxxxxxxxxxxxxxxxxxxxxxxxxxxxxxxxxxxxxxxxxxxxxxxxxxx
(defun procesatabla (lista / numfila)
  (setq numfila 1 numcol 0)
  (foreach campo (car lista)
    (datocelda numfila (setq numcol (+ 1 numcol))(car campo))
  )
  (while (setq fila (car lista))
    (setq numfila (+ 1 numfila) lista (cdr lista)
    )
  (procesafila fila numfila)
  )
)
;;;xxxxxxxxxxxxxxxxxxxxxxxxxxxxxxxxxxxxxxxxxxxxxxxxxxxxxxxxxxxxxxxxxxx
(defun lista->excel (lista / *celdaexcel* *hoja1* *coleccionhojas* *nuevolibro* *coleccionlibros* *aplexcel*)
  (setq oer *error* *error* appl-err)
  (vl-load-com)
  (iniciaexcel)
  (procesatabla lista)
  (terminaexcel)
;;;  (setq *error* oer)
)
;;;xxxxxxxxxxxxxxxxxxxxxxxxxxxxxxxxxxxxxxxxxxxxxxxxxxxxxxxxxxxxxxxxxxx

(defun c:excel (/ objetos cont ent lista claves)
  (setq objetos (ssget "x" (list (cons 0 "line"))))
  (setq cont 0)
  (while (setq ent (ssname objetos cont))
    (setq lista (cons (entget ent) lista))
    (setq cont (+ 1 cont))
  )
  (if (apply 'and (mapcar 'equal claves (cdr claves)))
    (lista->excel lista)
    (alert "! las entidades seleccionadas \no poseen igual formato!")
  )
  (princ)
)
