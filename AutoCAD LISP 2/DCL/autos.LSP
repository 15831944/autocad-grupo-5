(defun c:autos ()
  (setq VMIRROR nil
	file_ins nil
  )
  (setq indicador (load_dialog "d:/facultadI/dcl/autos.dcl"))
  (if (not (new_dialog "autos" indicador))
    (exit)
  )
;;;  xxxxxxxxxxxxxxxxxxxxxxxxxxxxxxxxxxxxxxxxxxxxxxxxxxxxxxxxxxxx
  (setq lista_autos (list "MERCEDES" "HYUNDAI" "FERRARI" "MAZDA"))
  (start_list "listas")
  (mapcar 'add_list lista_autos)
  (end_list)
  (action_tile "listas" "(elec)")
  (action_tile "valorradio" "(elec_radio)")
  (set_tile "espejo" "0")
  (action_tile "espejo" "(SETQ VMIRROR $value)")
;;;  boton ok-cancel
  (action_tile "cancel" "(done_dialog 0)")
  (action_tile "accept" "(done_dialog 1)")
;;;  xxxxxxxxxxxxxxxxxxxxxxxxxxxxxxxxxxxxxxxxxxxxxxxxxxxxxxxxxxxx
  (setq ventana_general (start_dialog))
  (unload_dialog indicador)
  (if (= ventana_general 0) (negado))
  (if (= ventana_general 1) (acepto))
)
;;;  xxxxxxxxxxxxxxxxxxxxxxxxxxxxxxxxxxxxxxxxxxxxxxxxxxxxxxxxxxxx
(defun elec ()
  (setq eleccion $VALUE)
  
  (setq x (dimx_tile "imagen")
	y (dimy_tile "imagen")
  )
  (setq elec_auto (strcat "d:/facultadI/slide/autos(auto" eleccion "0)"))
  (setq nro "0")
  (setq file_ins (strcat "d:\\facultadI\\bloques\\auto" eleccion nro ".dwg"))
  (start_image "imagen")
  (fill_image 0 0 x y 3)
  (slide_image 0 0 x y elec_auto)
  (end_image)
  (set_tile "valorradio" "eleccion00")
)
(defun elec_radio ()
  (setq valorradio $value)
  (setq nro (SUBSTR valorradio 10 1))
  (setq x (dimx_tile "imagen")
	y (dimy_tile "imagen")
  )
  (setq elec_auto (strcat "d:/facultadI/slide/autos(auto" eleccion  nro ")" ))
  (setq file_ins (strcat "d:/facultadI/bloques/auto" eleccion nro ".dwg"))
  (start_image "imagen")
  (fill_image 0 0 x y 3)
  (slide_image 0 0 x y elec_auto)
  (end_image)
)
(defun acepto ()
  (if file_ins
    (progn
       (prompt "\nInserte punto de Insercion")
       (command "insert"  file_ins pause "1" "1" 0)
    )  
  )
  (IF (= "1" VMIRROR)
    (COMMAND "MIRROR" (ENTLAST) "" (getvar "lastpoint") "@0,100" "y")
  )
  (PRINC)
)

(defun negado ()
  (alert "GRACIAS POR USAR EL PROGRAMA ")
  (PRINC)
)
