(defun c:esc1 ()
  (setq osmodo (getvar "osmode"))
  (setvar "osmode" 0)
  (setq	altura (getreal "\nIngrese la altura del escalon...")
	ancho  (getreal "\nIngrese la ancho del escalon...")
	gradas (getint "\nIngrese el numero de gradas del escalon...")
	p1     (getpoint "\nIngrese la base del escalon...")
  )
  (setq	p2 (polar p1 (/ pi 2) altura)
	p3 (polar p2 0 ancho)
  )
  (command "line" p1 p2 p3 "")
  (setvar "osmode" osmodo)
)
